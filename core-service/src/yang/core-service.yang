module core-service {
  namespace "http://com/example/core-service";
  prefix core-service;

  import ietf-inet-types {
    prefix inet;
  }
  import tailf-ncs {
    prefix ncs;
  }

  list core-service {
    key name;

    uses ncs:service-data;
    ncs:servicepoint "core-service";

    leaf name {
      type string;
    }
    
    list devices {
      key device;
      leaf device {
        type leafref {
          path "/ncs:devices/ncs:device/ncs:name";
        }
      }
      leaf ip_add_lo0 {
        type inet:ipv4-address;
        mandatory true;
      }


    }
    // may replace this with other ways of refering to the devices.

    // replace with your own stuff here
  }
}
